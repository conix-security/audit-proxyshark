-- $Id: CAP-U-ABORT-Data.asn 22239 2007-07-04 13:27:44Z etxrab $
-- 3GPP TS 29.078 7.3.0 (2006-06)
-- 5.7	User Abort Data
CAP-U-ABORT-Data {itu-t(0) identified-organization(4) etsi(0) mobileDomain(0) umts-network(1) modules(3) cap-u-abort-data(110) version5(4)}

DEFINITIONS ::= BEGIN

id-CAP-U-ABORT-Reason OBJECT IDENTIFIER ::= {itu-t(0) identified-organization(4) etsi(0) mobileDomain(0) umts-Network(1) as(1) cap-u-abort-reason(2) version3(2)}

cAP-U-ABORT-Reason-Abstract-Syntax ABSTRACT-SYNTAX ::= {CAP-U-ABORT-REASON IDENTIFIED BY
id-CAP-U-ABORT-Reason}

CAP-U-ABORT-REASON ::= ENUMERATED {
	no-reason-given				(1),
	application-timer-expired	(2),
	not-allowed-procedures		(3),
	abnormal-processing			(4),
	congestion					(5),
	invalid-reference			(6),
	missing-reference			(7),
	overlapping-dialogue		(8)
	}
-- application-timer-expired	shall be set when application timer (e.g. Tssf) is expired.
-- not-allowed-procedures		shall be set when received signal is not allowed in CAP
--								procedures.
--								For example, when a class 4 operation is received from the
--								gsmSCF and the operation is not allowed in gsmSSF FSM.
--								(gsmSSF FSM cannot continue state transition). (e.g. ReleaseCall
--								operation received in Waiting for End of Temporary Connection
--								state.)
-- abnormal-processing			shall be set when abnormal procedures occur at entity action.
-- congestion					shall be set when requested resource is unavailable due to
--								congestion at TC user (CAP) level.
-- invalid-reference			shall be set if the received destinationReference is unknown or
--								for a known destination Reference the received originationReference
--								does not match with the stored originationReference.
--								This abort reason is used for CAP defined GPRS-ReferenceNumber.
-- missing-reference			shall be set when the destinationReference or the
--								originationReference is absent in the received message but is
--								required to be present according to the procedures in
--								subclause 14.1.7.
--								This abort reason is used for CAP defined GPRS-ReferenceNumber.
-- overlapping-dialogue			shall be used by the gprsSSF to indicate to the gsmSCF that a
--								specific instance already has a TC dialogue open. This error
--								cause is typically obtained when both the gsmSCF and gprsSSF
--								open a new dialogue at the same time.
-- no-reason-given				shall be set when any other reasons above do not apply
END -- of CAP-U-ABORT-Data
