-- $Id: MSAccessProtocol.asn 23586 2007-11-25 17:46:42Z gal $
-- http://www.itu.int/ITU-T/asn1/database/itu-t/x/x419/1999/index.html
-- Module MSAccessProtocol (X.419:06/1999)
MSAccessProtocol {joint-iso-itu-t mhs(6) protocols(0) modules(0)
  ms-access-protocol(2) version-1999(1)} DEFINITIONS ::=
BEGIN

--	Prologue
IMPORTS
  -- MS Abstract Service
  ms-access-contract-88, ms-access-contract-94, ms-submission, retrieval,
    retrieval-88
    --==
    FROM MSAbstractService {joint-iso-itu-t mhs(6) ms(4) modules(0)
      abstract-service(1) version-1999(1)}
  -- Remote Operations
  APPLICATION-CONTEXT
    --==
    FROM Remote-Operations-Information-Objects-extensions {joint-iso-itu-t
      remote-operations(4) informationObjects-extensions(8) version1(0)}
  Code
    --==
    FROM Remote-Operations-Information-Objects {joint-iso-itu-t
      remote-operations(4) informationObjects(5) version1(0)}
  Bind{}, InvokeId, Unbind{}
    --==
    FROM Remote-Operations-Generic-ROS-PDUs {joint-iso-itu-t
      remote-operations(4) generic-ROS-PDUs(6) version1(0)}
  ROS-SingleAS{}
    --==
    FROM Remote-Operations-Useful-Definitions {joint-iso-itu-t
      remote-operations(4) useful-definitions(7) version1(0)}
  acse, association-by-RTSE, pData, transfer-by-RTSE
    --==
    FROM Remote-Operations-Realizations {joint-iso-itu-t remote-operations(4)
      realizations(9) version1(0)}
  acse-abstract-syntax
    --==
    FROM Remote-Operations-Abstract-Syntaxes {joint-iso-itu-t
      remote-operations(4) remote-operations-abstract-syntaxes(12) version1(0)}
  -- Reliable Transfer
  RTORQapdu, RTOACapdu, RTORJapdu
    FROM Reliable-Transfer-APDU {joint-iso-itu-t reliable-transfer(3) apdus(0)}
  -- MTS Access Protocol
  message-administration-abstract-syntax-88,
    message-administration-abstract-syntax-94,
    message-submission-abstract-syntax
    --==
    FROM MTSAccessProtocol {joint-iso-itu-t mhs(6) protocols(0) modules(0)
      mts-access-protocol(1) version-1999(1)}
  -- Object Identifiers
  id-ac-ms-access-88, id-ac-ms-access-94, id-ac-ms-reliable-access-88,
    id-ac-ms-reliable-access-94, id-as-ms-msse, id-as-mase-88, id-as-mase-94,
    id-as-mdse-88, id-as-mdse-94, id-as-mrse-88, id-as-mrse-94, id-as-ms-88,
    id-as-ms-94, id-as-ms-rtse, id-as-msse
    --==
    FROM MHSProtocolObjectIdentifiers {joint-iso-itu-t mhs(6) protocols(0)
      modules(0) object-identifiers(0) version-1994(0)};

RTSE-apdus ::= CHOICE {
  rtorq-apdu  [16] IMPLICIT RTORQapdu,
  rtoac-apdu  [17] IMPLICIT RTOACapdu,
  rtorj-apdu  [18] IMPLICIT RTORJapdu,
  rttp-apdu   RTTPapdu,
  rttr-apdu   RTTRapdu,
  rtab-apdu   [22] IMPLICIT RTABapdu
}

RTTPapdu ::= -- priority-- INTEGER

RTTRapdu ::= OCTET STRING

RTABapdu ::= SET {
  abortReason         [0] IMPLICIT AbortReason OPTIONAL,
  reflectedParameter  [1] IMPLICIT BIT STRING OPTIONAL,
  -- 8 bits maximum, only if abortReason is invalidParameter
  userdataAB
    [2]  TYPE-IDENTIFIER.&Type
      OPTIONAL -- only in normal mode and if abortReason--
  -- is userError 
}

AbortReason ::= INTEGER {
  localSystemProblem(0),
  invalidParameter(1), -- reflectedParameter supplied
  unrecognizedActivity(2),
  temporaryProblem(3),
  -- the RTSE cannot accept a session for a period of time
  protocolError(4), -- RTSE level protocol error
  permanentProblem(5), --provider-abort solely in normal mode 
  userError(6), -- user-abort solely in normal mode
  transferCompleted(7) -- activity can't be discarded--}

--	APPLICATION-CONTEXTS
--	1994 Application Context omitting RTSE
ms-access-94 APPLICATION-CONTEXT ::= {
  CONTRACT                  ms-access-contract-94
  ESTABLISHED BY            acse
  INFORMATION TRANSFER BY   pData
  ABSTRACT SYNTAXES
    {acse-abstract-syntax | ms-message-submission-abstract-syntax |
      message-retrieval-abstract-syntax-94 |
      message-administration-abstract-syntax-94 |
      ms-bind-unbind-abstract-syntax-94}
  APPLICATION CONTEXT NAME  id-ac-ms-access-94
}

--	1994 Application Context including RTSE
ms-reliable-access-94 APPLICATION-CONTEXT ::= {
  CONTRACT                  ms-access-contract-94
  ESTABLISHED BY            association-by-RTSE
  INFORMATION TRANSFER BY   transfer-by-RTSE
  ABSTRACT SYNTAXES
    {acse-abstract-syntax | ms-message-submission-abstract-syntax |
      message-retrieval-abstract-syntax-94 |
      message-administration-abstract-syntax-94 |
      ms-bind-unbind-rtse-abstract-syntax}
  APPLICATION CONTEXT NAME  id-ac-ms-reliable-access-94
}

--	1988 Application Context omitting RTSE
ms-access-88 APPLICATION-CONTEXT ::= {
  CONTRACT                  ms-access-contract-88
  ESTABLISHED BY            acse
  INFORMATION TRANSFER BY   pData
  ABSTRACT SYNTAXES
    {acse-abstract-syntax | message-submission-abstract-syntax |
      message-retrieval-abstract-syntax-88 |
      message-administration-abstract-syntax-88 |
      ms-bind-unbind-abstract-syntax-88}
  APPLICATION CONTEXT NAME  id-ac-ms-access-88
}

--	1988 Application Context including RTSE
ms-reliable-access-88 APPLICATION-CONTEXT ::= {
  CONTRACT                  ms-access-contract-88
  ESTABLISHED BY            association-by-RTSE
  INFORMATION TRANSFER BY   transfer-by-RTSE
  ABSTRACT SYNTAXES
    {acse-abstract-syntax | message-submission-abstract-syntax |
      message-retrieval-abstract-syntax-88 |
      message-administration-abstract-syntax-88 |
      ms-bind-unbind-rtse-abstract-syntax}
  APPLICATION CONTEXT NAME  id-ac-ms-reliable-access-88
}

--	ABSTRACT SYNTAXES
--	Abstract-syntax for 1994 MS-bind and MS-unbind
ms-bind-unbind-abstract-syntax-94 ABSTRACT-SYNTAX ::= {
  MSBindUnbindPDUs94
  IDENTIFIED BY  id-as-ms-94
}

--MSBindUnbindPDUs94 ::= CHOICE {
--  bind    Bind{ms-access-contract-94.&connection.&bind},
--  unbind  Unbind{ms-access-contract-94.&connection.&unbind}
--}

--	Abstract-syntax for 1988 MS-bind and MS-unbind
ms-bind-unbind-abstract-syntax-88 ABSTRACT-SYNTAX ::= {
  MSBindUnbindPDUs88
  IDENTIFIED BY  id-as-ms-88
}

--MSBindUnbindPDUs88 ::= CHOICE {
--  bind    Bind{ms-access-contract-88.&connection.&bind},
--  unbind  Unbind{ms-access-contract-88.&connection.&unbind}
--}

--	Abstract-syntax for MS-bind and MS-unbind with RTSE 
ms-bind-unbind-rtse-abstract-syntax ABSTRACT-SYNTAX ::= {
  RTSE-apdus -- With MS-bind and MS-unbind --
  IDENTIFIED BY  id-as-ms-rtse
}

--	Abstract Syntax for MS Message Submission Service Element
ms-message-submission-abstract-syntax ABSTRACT-SYNTAX ::= {
  MSMessageSubmissionPDUs
  IDENTIFIED BY  id-as-ms-msse
}

--MSMessageSubmissionPDUs ::= ROS-SingleAS{{MSInvokeIds}, ms-submission}

--MSInvokeIds ::= InvokeId(ALL EXCEPT absent:NULL) 

--	Abstract Syntax for Message Retrieval Service Element 1994
--message-retrieval-abstract-syntax-94 ABSTRACT-SYNTAX ::= {
--  MessageRetrievalPDUs
--  IDENTIFIED BY  id-as-mrse-94
--}

--	Abstract Syntax for Message Retrieval Service Element 1988
--MessageRetrievalPDUs ::=
--  ROS-SingleAS{{MSInvokeIds}, retrieval}

--message-retrieval-abstract-syntax-88 ABSTRACT-SYNTAX ::= {
--  MessageRetrievalPDUs88
--  IDENTIFIED BY  id-as-mrse-88
--}

--MessageRetrievalPDUs88 ::= ROS-SingleAS{{MSInvokeIds}, retrieval-88}

--	Remote Operations
op-ms-submission-control Code ::= local:2

op-ms-message-submission Code ::= local:3

op-ms-probe-submission Code ::= local:4

op-ms-cancel-deferred-delivery Code ::= local:7

op-summarize Code ::= local:20

op-list Code ::= local:21

op-fetch Code ::= local:22

op-delete Code ::= local:23

op-register-ms Code ::= local:24

op-alert Code ::= local:25

op-modify Code ::= local:26

--	Remote Errors
err-attribute-error Code ::= local:21

err-auto-action-request-error Code ::= local:22

err-delete-error Code ::= local:23

err-fetch-restriction-error Code ::= local:24

err-range-error Code ::= local:25 -- 1988 Application Contexts only 

err-security-error Code ::= local:26

err-service-error Code ::= local:27

err-sequence-number-error Code ::= local:28

err-invalid-parameters-error Code ::= local:29

err-message-group-error Code ::= local:30

err-ms-extension-error Code ::= local:31

err-register-ms-error Code ::= local:32

err-modify-error Code ::= local:33

err-entry-class-error Code ::= local:34

END -- of MSAccessProtocol

-- Generated by Asnp, the ASN.1 pretty-printer of France Telecom R&D
