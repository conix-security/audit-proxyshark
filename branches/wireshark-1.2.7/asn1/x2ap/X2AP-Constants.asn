-- $Id: X2AP-Constants.asn 26271 2008-09-25 19:20:14Z etxrab $
-- 3GPP TS 36.423 V8.3.0 (2008-09)
-- 9.3.7	Constant Definitions
-- **************************************************************
--
-- Constant definitions
--
-- **************************************************************

X2AP-Constants {
itu-t (0) identified-organization (4) etsi (0) mobileDomain (0) 
eps-Access (21) modules (3) x2ap (2) version1 (1) x2ap-Constants (4) }

DEFINITIONS AUTOMATIC TAGS ::= 

BEGIN

IMPORTS
	ProcedureCode,
	ProtocolIE-ID
FROM X2AP-CommonDataTypes;

-- **************************************************************
--
-- Elementary Procedures
--
-- **************************************************************

id-handoverPreparation											ProcedureCode ::= 0
id-handoverCancel												ProcedureCode ::= 1
id-loadIndication												ProcedureCode ::= 2
id-errorIndication												ProcedureCode ::= 3
id-snStatusTransfer												ProcedureCode ::= 4
id-uEContextRelease									ProcedureCode ::= 5
id-x2Setup														ProcedureCode ::= 6
id-reset														ProcedureCode ::= 7
id-eNBConfigurationUpdate										ProcedureCode ::= 8
id-resourceStatusUpdateInitiation								ProcedureCode ::= 9
id-resourceStatusReporting										ProcedureCode ::= 10





-- **************************************************************
--
-- Lists
--
-- **************************************************************

maxEARFCN									INTEGER ::= 32767	-- FFS Value to be checked
maxInterfaces								INTEGER ::= 16		-- FFS Value to be checked
maxCellineNB								INTEGER ::= 256		
maxnoofCells								INTEGER ::= 16		-- FFS Value to be checked
maxnoofBearers								INTEGER ::= 256		
maxNrOfErrors								INTEGER ::= 256		-- FFS Value to be checked
maxnoofPDCP-SN								INTEGER ::= 16		-- FFS Value to be checked
maxnoofEPLMNs								INTEGER ::= 15		
maxnoofEPLMNsPlusOne						INTEGER ::= 16		
maxnoofForbLACs								INTEGER ::= 4096		
maxnoofForbTACs							    INTEGER ::= 4096	
maxnoofBPLMNs								INTEGER ::= 6
maxnoofPRBs									INTEGER ::= 110		-- FFS Value to be checked
maxPools									INTEGER ::= 16		-- FFS Value to be checked




-- **************************************************************
--
-- IEs
--
-- **************************************************************

id-Bearers-Admitted-Item													ProtocolIE-ID ::= 0
id-Bearers-Admitted-List													ProtocolIE-ID ::= 1
id-Bearers-NotAdmitted-Item													ProtocolIE-ID ::= 2
id-Bearers-NotAdmitted-List													ProtocolIE-ID ::= 3
id-Bearers-ToBeSetup-Item													ProtocolIE-ID ::= 4
id-Cause																	ProtocolIE-ID ::= 5
id-CellInformation															ProtocolIE-ID ::= 6
id-CellInformation-Item														ProtocolIE-ID ::= 7
id-InterfacesToTrace-Item													ProtocolIE-ID ::= 8
id-New-eNB-UE-X2AP-ID														ProtocolIE-ID ::= 9
id-Old-eNB-UE-X2AP-ID														ProtocolIE-ID ::= 10
id-TargetCell-ID															ProtocolIE-ID ::= 11
id-TargeteNBtoSource-eNBTransparentContainer								ProtocolIE-ID ::= 12
id-TraceActivation															ProtocolIE-ID ::= 13
id-UE-ContextInformation													ProtocolIE-ID ::= 14
id-UE-HistoryInformation													ProtocolIE-ID ::= 15
id-UE-X2AP-ID																ProtocolIE-ID ::= 16
id-CriticalityDiagnostics													ProtocolIE-ID ::= 17
id-Bearers-SubjectToStatusTransfer-List										ProtocolIE-ID ::= 18
id-Bearers-SubjectToStatusTransfer-Item										ProtocolIE-ID ::= 19
id-ServedCells																ProtocolIE-ID ::= 20
id-GlobalENB-ID																ProtocolIE-ID ::= 21
id-TimeToWait																ProtocolIE-ID ::= 22
id-GUMMEI-ID																ProtocolIE-ID ::= 23
id-GUGroupIDList															ProtocolIE-ID ::= 24
id-ServedCellsToAdd															ProtocolIE-ID ::= 25
id-ServedCellsToModify														ProtocolIE-ID ::= 26
id-ServedCellsToDelete														ProtocolIE-ID ::= 27
id-Registration-Request														ProtocolIE-ID ::= 28
id-CellToReport																ProtocolIE-ID ::= 29
id-ReportingPeriodicity														ProtocolIE-ID ::= 30
id-CellToReport-Item														ProtocolIE-ID ::= 31
id-CellMeasurementResult													ProtocolIE-ID ::= 32
id-CellMeasurementResult-Item												ProtocolIE-ID ::= 33
id-GUGroupIDListToAdd														ProtocolIE-ID ::= 34
id-GUGroupIDListToDelete													ProtocolIE-ID ::= 35


END
