-- 3GPP TS 36.331 V8.4.0 Release 8
-- $Id: EUTRA-UE-Variables.asn 27179 2009-01-07 19:59:31Z etxrab $
--
EUTRA-UE-Variables DEFINITIONS AUTOMATIC TAGS ::=
 
BEGIN


VarMeasurementConfiguration ::=		SEQUENCE {
	-- Measurement identities
	measIdList							MeasIdToAddModifyList				OPTIONAL,
	-- Measurement objects
	measObjectList						MeasObjectToAddModifyList			OPTIONAL,
	-- Reporting configurations
	reportConfigList					ReportConfigToAddModifyList			OPTIONAL,
	-- Other parameters
	quantityConfig						QuantityConfig						OPTIONAL,
	s-Measure							RSRP-Range							OPTIONAL,
	cdma2000-SystemTimeInfo				CDMA2000-SystemTimeInfo				OPTIONAL,
	neighbourCellConfiguration			NeighbourCellConfiguration			OPTIONAL,
	speedDependentParameters			SEQUENCE {
		mobilityStateParameters				MobilityStateParameters,
		speedDependentScalingParameters		ConnectedModeSpeedDependentScalingParameters
	}																		OPTIONAL
}


VarMeasurementReports ::=				SEQUENCE (SIZE (1..maxMeasId)) OF SEQUENCE {
	-- List of measurement that have been triggered
	measId								MeasId,
	cellsTriggeredList					CellsTriggeredList				OPTIONAL,
	numberOfReportsSent					INTEGER
}

CellsTriggeredList ::=				SEQUENCE (SIZE (1..maxCellMeas)) OF SEQUENCE {
	cellIdentity						PhysicalCellIdentity
}


VarShortMAC-Input ::=					SEQUENCE {
	cellIdentity							CellIdentity,
	physicalCellIdentity					PhysicalCellIdentity,
	c-RNTI									C-RNTI
}



END
